/* EXPECT: APPLICABILITY  - #operation (action = Performance) on an item def (Object): Performance is disjoint from Object */
package N18 {
	private import UML3Core::*;
	#operation item def NotBehavior;
}
