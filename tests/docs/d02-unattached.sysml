package DocsUnattached {
	doc
	/*
	Package doc.
	Contents:
	- A: a part definition.
	*/
	/* A loose comment that looks like it describes A but annotates the package. */
	part def A { doc /* A. */ }
}
