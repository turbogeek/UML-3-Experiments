package DocsCitation {
	doc
	/*
	Cites a clause that does not exist.
	Contents:
	- A: a part definition.
	References: KerML 99.9.9; UML 2.5.1 NoSuchMetaclass; UML3Core::NoSuchElement; E99.
	*/
	part def A { doc /* A. */ }
}
