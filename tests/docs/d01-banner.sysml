package DocsBanner {
	doc
	/* =========================================
	   Section with a banner
	   Contents:
	   - A: a part definition.
	   ========================================= */
	part def A { doc /* A. */ }
}
