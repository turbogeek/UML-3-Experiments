package DocFixtureCrossFileA {
	doc
	/*
	DocFixtureCrossFileA: the element that a comment in another file of the same model is about.

	Contents:
	- Sensor: a part definition.
	*/
	part def Sensor {
		doc /* A sensor. */
	}
}
